ROOMGUARD-MIB DEFINITIONS ::= BEGIN

-- 1.3.6.1.4.1.<PEN>.1 = RoomGuard

-- 1.3.6.1.4.1.<PEN>.1.1 = WiFi
-- 1.3.6.1.4.1.<PEN>.1.1.1 = SSID
-- 1.3.6.1.4.1.<PEN>.1.1.2 = Status
-- 1.3.6.1.4.1.<PEN>.1.1.3 = Signal

-- 1.3.6.1.4.1.<PEN>.1.2 = Sensors
-- 1.3.6.1.4.1.<PEN>.1.2.1 = Sensor_0 (default sensor)
-- 1.3.6.1.4.1.<PEN>.1.2.1.1 = Sensor_0 Temperature (°C)
-- 1.3.6.1.4.1.<PEN>.1.2.1.2 = Sensor_0 Humidity (% rel.)

-- 1.3.6.1.4.1.<PEN>.1.99 = Experimental Scope

-- 1.3.6.1.4.1.<PEN>.1.100 = System
-- 1.3.6.1.4.1.<PEN>.1.100.1 = MemTotal
-- 1.3.6.1.4.1.<PEN>.1.100.2 = MemFree

ANSnullANS MODULE-IDENTITY
	LAST-UPDATED "202105220000Z"
	ORGANIZATION "ANSnullANS.org"
	CONTACT-INFO
		"postal:	Paco Lechner
					Grenadiergasse 36/9
					8020 Graz
					Austria
					
		 email:		contact@ansnullans.org"
	DESCRIPTION
		"RoomGuard MIB Objects."
	REVISION     "200406150000Z"
	DESCRIPTION
		"First Draft"
	::= { enterprises 57477 }

-- RoomGuard Sub-Object of ANSnullANS.org PEN	
RoomGuard		OBJECT IDENTIFIER ::= { ANSnullANS 1 }

-- WiFi Related Items
WiFiStatus OBJECT-TYPE
	SYNTAX		OBJECT IDENTIFIER
	MAX-ACCESS	read-only
	STATUS		current
	DESCRIPTION
		"WiFi Information"
	::= { RoomGuard 1 }

SSID OBJECT-TYPE
	SYNTAX		DisplayString
	MAX-ACCESS	read-only
	STATUS		current
	DESCRIPTION
		"Configured SSID"
	::= { WiFiStatus 1 }
	
Status OBJECT-TYPE
	SYNTAX		DisplayString
	MAX-ACCESS	read-only
	STATUS		current
	DESCRIPTION
		"Current WiFi Status"
	::= { WiFiStatus 2 }
	
Signal OBJECT-TYPE
	SYNTAX		Integer32
	MAX-ACCESS	read-only
	STATUS		current
	DESCRIPTION
		"WiFi Signal Strength"
	::= { WiFiStatus 3 }


-- Sensor Items
Sensors	OBJECT-TYPE
	SYNTAX 		OBJECT IDENTIFIER
	MAX-ACCESS	read-only
	STATUS		current
	DESCRIPTION
		"DHT Sensor inside RoomGuard"
	::= { RoomGuard 2 }
	
Sensor0	OBJECT-TYPE
	SYNTAX 		OBJECT IDENTIFIER
	MAX-ACCESS	read-only
	STATUS		current
	DESCRIPTION
		"DHT Sensor inside RoomGuard"
	::= { Sensors 1 }

Temperature0 OBJECT-TYPE
	SYNTAX		INTEGER
	MAX-ACCESS	read-only
	STATUS		current
	DESCRIPTION
		"Temperature from Sensor 0"
	DEFVAL { 0 }
	::= { Sensor0 1 }

Temperature0 ::= TEXTUAL-CONVENTION
	DISPLAY-HINT	"d-1"
	STATUS			current
	DESCRIPTION
		"Temperature"
	SYNTAX INTEGER
	
Humidity0 OBJECT-TYPE
	SYNTAX		Integer32
	MAX-ACCESS	read-only
	STATUS		current
	DESCRIPTION
		"Temperature from Sensor"
	DEFVAL { 0 }
	::= { Sensor0 2 }
	
System OBJECT-TYPE
	SYNTAX		OBJECT IDENTIFIER
	MAX-ACCESS	read-only
	STATUS		current
	DESCRIPTION
		"Scope for Experimental functions that are not part of main RoomGuard Repository"
	::= { RoomGuard 100 }
	
MemTotal OBJECT-TYPE
	SYNTAX		Integer32
	MAX-ACCESS	read-only
	STATUS		current
	DESCRIPTION
		"Total RAM in Bytes"
	DEFVAL { 0 }
	::= { System 1 }

MemFree OBJECT-TYPE
	SYNTAX		Integer32
	MAX-ACCESS	read-only
	STATUS		current
	DESCRIPTION
		"Free RAM in Bytes"
	DEFVAL { 0 }
	::= { System 2 }
	
-- Scope for Experimental functions of RoomGuard
Experimental OBJECT-TYPE
	SYNTAX		OBJECT IDENTIFIER
	MAX-ACCESS	read-only
	STATUS		current
	DESCRIPTION
		"Scope for Experimental functions that are not part of main RoomGuard Repository"
	::= { RoomGuard 99 }
	
END
